FMANALYSER-MIB DEFINITIONS ::= BEGIN


IMPORTS
    MODULE-COMPLIANCE, OBJECT-GROUP
    	FROM SNMPv2-CONF
    enterprises, MODULE-IDENTITY, OBJECT-TYPE,
    Integer32
        FROM SNMPv2-SMI;


fmanalyser MODULE-IDENTITY
    LAST-UPDATED    "201204281527Z"
    ORGANIZATION    "Gaftech"
    CONTACT-INFO    "gabriel@gaftech.fr"
    DESCRIPTION     "The MIB module for fmanalyser snmp plugin"
    REVISION        "201204281527Z"
    DESCRIPTION     "auto-generated revision with fmanalyser 0.1.dev"
    ::= { gaftech 1 }

gaftech OBJECT IDENTIFIER ::= { enterprises 999999 }

-- Root nodes ****************************************
device		OBJECT IDENTIFIER ::= { fmanalyser 1 }
analyser	OBJECT IDENTIFIER ::= { fmanalyser 2 }
software	OBJECT IDENTIFIER ::= { fmanalyser 8 }
conformance OBJECT IDENTIFIER ::= { fmanalyser 9 }


-- Software infos ************************************
softVersion OBJECT-TYPE
    SYNTAX        OCTET STRING
    MAX-ACCESS    read-only
    STATUS        current
    DESCRIPTION   "fmanalyser software version"
    ::= { software 1 }

-- Device status *************************************
online OBJECT-TYPE
    SYNTAX        Integer32(0..1)
    MAX-ACCESS    read-only
    STATUS        current
    DESCRIPTION
        "The device online/offline status."
    ::= { device 2 }

-- Measurements **************************************


-- Conformance information ***************************
compliances OBJECT IDENTIFIER ::= { conformance 1 }
groups		OBJECT IDENTIFIER ::= { conformance 2 }

staticValues OBJECT-GROUP
	OBJECTS 	{softVersion}
	STATUS		current
	DESCRIPTION	"static informations"
	::= { groups 1 }

liveValues OBJECT-GROUP
	OBJECTS		{online}
	STATUS		current
	DESCRIPTION	"live informations"
	::= { groups 2 }
	
cachedValues OBJECT-GROUP
	OBJECTS		{}
	STATUS		current
	DESCRIPTION	"cached informations"
	::= { groups 3 }

mibCompliance MODULE-COMPLIANCE
	STATUS		current
	DESCRIPTION	"our compliance"
	MODULE
	MANDATORY-GROUPS {staticValues, liveValues, cachedValues}
	::= { compliances 1 }






END
